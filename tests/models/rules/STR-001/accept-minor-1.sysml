// Test model of story #157: STR-001 accepts this model.
// The root package gives the DSML version 1.1, the minor version of the
// library 1.1.0.
package Str001AcceptMinor1 {
    private import DSML::*;
    @DsmlVersion { major = 1; minor = 1; }

    #Stakeholder part def ShopOwner;
}
