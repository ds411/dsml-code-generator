// Test model of story #59: STR-001 accepts this model.
// The root package gives the DSML version 1.0.
package Str001Accept {
    private import DSML::*;
    @DsmlVersion { major = 1; minor = 0; }

    #Stakeholder part def ShopOwner;
}
