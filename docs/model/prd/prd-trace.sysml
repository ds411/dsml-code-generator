package PrdTrace {
    private import DSML::*;
    private import PrdNeeds::*;

    #Requirement requirement <'PRD-TRACE-001'> trace001 {
        doc /* The model must use these link types: the stakeholder member of a need, frame, #derivation, #refinement, satisfy, allocate, #Realizes and verify. */
        :>> title = "Link types"; :>> kind = RequirementKind::functional; :>> priority = Priority::must; :>> status = Status::draft;
        frame traceability;
    }
    #Requirement requirement <'PRD-TRACE-002'> trace002 {
        doc /* A satisfy link can come from an application element or from an infrastructure element. */
        :>> title = "Satisfy sources"; :>> kind = RequirementKind::functional; :>> priority = Priority::must; :>> status = Status::draft;
        frame traceability;
    }
    #Requirement requirement <'PRD-TRACE-003'> trace003 {
        doc /* The IR must hold each link with its type and the identities of its source and target. */
        :>> title = "Links in IR"; :>> kind = RequirementKind::functional; :>> priority = Priority::must; :>> status = Status::draft;
        frame traceability;
    }
    #Requirement requirement <'PRD-TRACE-004'> trace004 {
        doc /* The traceability engine must follow links in the two directions: from a need to its code, tests and AWS resources, and from a file or resource back to its needs. */
        :>> title = "Two-way tracing"; :>> kind = RequirementKind::functional; :>> priority = Priority::must; :>> status = Status::draft;
        frame traceability;
    }
    #Requirement requirement <'PRD-TRACE-005'> trace005 {
        doc /* Each generated source file that permits comments must start with a header: the line Generated by dsml <major>. Do not edit., then the line Elements: with the identities of its model elements in sorted order. */
        :>> title = "File header"; :>> kind = RequirementKind::functional; :>> priority = Priority::must; :>> status = Status::draft;
        frame traceability;
    }
    #Requirement requirement <'PRD-TRACE-006'> trace006 {
        doc /* The generator must write the trace manifest .dsml/trace.gen.json. For each element, it must give each generated file, each symbol in that file (class, function, route or HCL resource address) and the line range of the symbol. */
        :>> title = "Trace manifest"; :>> kind = RequirementKind::functional; :>> priority = Priority::must; :>> status = Status::draft;
        frame traceability;
    }
    #Requirement requirement <'PRD-TRACE-007'> trace007 {
        doc /* The trace manifest must give the HCL resource addresses of each infrastructure element, so a person can find the AWS resources of an element from its dsml:element tag or from its address. */
        :>> title = "HCL addresses in manifest"; :>> kind = RequirementKind::functional; :>> priority = Priority::must; :>> status = Status::draft;
        frame traceability;
    }
    #Requirement requirement <'PRD-TRACE-008'> trace008 {
        doc /* The trace manifest must be sorted by element identity, then by file path, then by line. */
        :>> title = "Sorted manifest"; :>> kind = RequirementKind::'constraint'; :>> priority = Priority::must; :>> status = Status::draft;
        frame deterministicGeneration;
    }
    #Requirement requirement <'PRD-TRACE-009'> trace009 {
        doc /* A trace comment must be a line comment with the form trace: <ID>[, <ID>]: # trace: R-001 in Python, HCL and YAML, and // trace: R-001 in TypeScript. An ID can be a short name or a qualified name. */
        :>> title = "Trace comment form"; :>> kind = RequirementKind::'interface'; :>> priority = Priority::must; :>> status = Status::draft;
        frame traceability;
    }
    #Requirement requirement <'PRD-TRACE-010'> trace010 {
        doc /* The toolchain must read trace comments in the hand-written files of the output folders and of the test folders in the configuration file. It must not read generated files for trace comments. */
        :>> title = "Trace comment scan"; :>> kind = RequirementKind::functional; :>> priority = Priority::must; :>> status = Status::draft;
        frame traceability;
    }
    #Requirement requirement <'PRD-TRACE-011'> trace011 {
        doc /* A trace comment applies to the next symbol in the file. If no symbol follows, it applies to the file. */
        :>> title = "Trace comment scope"; :>> kind = RequirementKind::functional; :>> priority = Priority::must; :>> status = Status::draft;
        frame traceability;
    }
    #Requirement requirement <'PRD-TRACE-012'> trace012 {
        doc /* The orphan report must list each trace comment with an ID that is not in the model. */
        :>> title = "Unknown trace IDs"; :>> kind = RequirementKind::functional; :>> priority = Priority::must; :>> status = Status::draft;
        frame traceability;
    }
    #Requirement requirement <'PRD-TRACE-013'> trace013 {
        doc /* dsml trace must write the four reports coverage, orphans, impact and suspect in the table of the section "Reports". */
        :>> title = "Four reports"; :>> kind = RequirementKind::functional; :>> priority = Priority::must; :>> status = Status::draft;
        frame traceability;
    }
    #Requirement requirement <'PRD-TRACE-014'> trace014 {
        doc /* The coverage report must give each requirement one status: missing (no satisfying element), satisfied (a satisfying element, no verification) or verified (a satisfying element and a verification). */
        :>> title = "Coverage status"; :>> kind = RequirementKind::functional; :>> priority = Priority::must; :>> status = Status::draft;
        frame traceability;
    }
    #Requirement requirement <'PRD-TRACE-015'> trace015 {
        doc /* An element must count as changed if the hash of its IR form, with no source locations, is different from the hash in the baseline. */
        :>> title = "Change detection"; :>> kind = RequirementKind::functional; :>> priority = Priority::must; :>> status = Status::draft;
        frame traceability;
    }
    #Requirement requirement <'PRD-TRACE-016'> trace016 {
        doc /* The impact and suspect reports must use the baseline that --baseline gives, or the default baseline that decision record 03 gives. */
        :>> title = "Report baseline"; :>> kind = RequirementKind::functional; :>> priority = Priority::must; :>> status = Status::draft;
        frame traceability;
    }
    #Requirement requirement <'PRD-TRACE-017'> trace017 {
        doc /* Each report must be available as HTML, CSV and JSON. The HTML report must be one file with no external resources. */
        :>> title = "Report formats"; :>> kind = RequirementKind::'interface'; :>> priority = Priority::must; :>> status = Status::draft;
        frame traceability;
    }
    #Requirement requirement <'PRD-TRACE-018'> trace018 {
        doc /* Each report must give the model commit and the baseline commit, and no date or time. */
        :>> title = "Report commits"; :>> kind = RequirementKind::'constraint'; :>> priority = Priority::must; :>> status = Status::draft;
        frame deterministicGeneration;
    }
}
